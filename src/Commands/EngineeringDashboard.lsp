(setq *FloorPropData* '(
  (500 ((690 2000) (790 1750) (920 1500) (1100 1250) (1380 1000)))
  (450 ((670 2250) (760 2000) (870 1750) (1010 1500) (1210 1250) (1520 1000)))
  (400 ((750 2250) (840 2000) (970 1750) (1130 1500) (1350 1250) (1690 1000)))
  (350 ((760 2500) (850 2250) (950 2000) (1090 1750) (1270 1500) (1520 1250) (1910 1000)))
  (300 ((870 2500) (970 2250) (1090 2000) (1250 1750) (1460 1500) (1750 1250) (2080 1000)))
  (280 ((920 2500) (1030 2250) (1150 2000) (1320 1750) (1540 1500) (1850 1250) (2130 1000)))
  (260 ((890 2750) (980 2500) (1090 2250) (1220 2000) (1400 1750) (1630 1500) (1960 1250) (2180 1000)))
  (240 ((950 2750) (1040 2500) (1160 2250) (1300 2000) (1490 1750) (1730 1500) (2040 1250) (2240 1000)))
  (220 ((1010 2750) (1110 2500) (1240 2250) (1390 2000) (1590 1750) (1850 1500) (2110 1250) (2300 1000)))
  (200 ((1080 2750) (1190 2500) (1330 2250) (1490 2000) (1700 1750) (1990 1500) (2180 1250) (2370 1000)))
))

(setq *PropCapacities* '(
  (5.5 ("550 at bottom" . 20.6) ("550 at top" . 22.7))
  (5.4 ("550 at bottom" . 21.6) ("550 at top" . 23.9))
  (5.3 ("550 at bottom" . 22.5) ("550 at top" . 25.2))
  (5.2 ("550 at bottom" . 23.6) ("550 at top" . 26.5))
  (5.1 ("550 at bottom" . 24.7) ("550 at top" . 27.9))
  (5.0 ("550 at bottom" . 25.8) ("550 at top" . 29.4))
  (4.9 ("550 at bottom" . 27.2) ("550 at top" . 31.0))
  (4.8 ("550 at bottom" . 28.7) ("550 at top" . 32.5))
  (4.7 ("550 at bottom" . 30.1) ("550 at top" . 34.2))
  (4.6 ("550 at bottom" . 31.6) ("550 at top" . 35.9))
  (4.5 ("550 at bottom" . 33.2) ("550 at top" . 36.7))
  (4.4 ("550 at bottom" . 34.9) ("550 at top" . 36.7))
  (4.3 ("550 at bottom" . 36.7) ("550 at top" . 36.7))
  (4.2 ("550 at bottom" . 36.7) ("550 at top" . 36.7))
  (4.1 ("550 at bottom" . 36.7) ("550 at top" . 36.7))
  (4.0 ("400 at bottom" . 21.5) ("400 at top" . 24.8) ("550 at bottom" . 36.7) ("550 at top" . 36.7))
  (3.9 ("400 at bottom" . 23.0) ("400 at top" . 26.8) ("550 at bottom" . 36.7) ("550 at top" . 36.7))
  (3.8 ("400 at bottom" . 24.4) ("400 at top" . 28.7) ("550 at bottom" . 36.7) ("550 at top" . 36.7))
  (3.7 ("400 at bottom" . 26.0) ("400 at top" . 30.8) ("550 at bottom" . 36.7) ("550 at top" . 36.7))
  (3.6 ("400 at bottom" . 27.7) ("400 at top" . 33.2) ("550 at bottom" . 36.7) ("550 at top" . 36.7))
  (3.5 ("350 at bottom" . 20.8) ("350 at top" . 24.5) ("400 at bottom" . 29.4) ("400 at top" . 35.5) ("550 at bottom" . 36.7) ("550 at top" . 36.7))
  (3.4 ("350 at bottom" . 22.3) ("350 at top" . 26.7) ("400 at bottom" . 31.0) ("400 at top" . 36.7) ("550 at bottom" . 36.7) ("550 at top" . 36.7))
  (3.3 ("350 at bottom" . 23.8) ("350 at top" . 28.9) ("400 at bottom" . 32.4) ("400 at top" . 36.7) ("550 at bottom" . 36.7) ("550 at top" . 36.7))
  (3.2 ("350 at bottom" . 25.4) ("350 at top" . 31.3) ("400 at bottom" . 33.5) ("400 at top" . 36.7) ("550 at bottom" . 36.7) ("550 at top" . 36.7))
  (3.1 ("350 at bottom" . 27.1) ("350 at top" . 34.0) ("400 at bottom" . 34.5) ("400 at top" . 36.7) ("550 at bottom" . 36.7) ("550 at top" . 36.7))
  (3.0 ("300 at bottom" . 20.7) ("300 at top" . 24.8) ("350 at bottom" . 28.8) ("350 at top" . 36.7) ("400 at bottom" . 35.5) ("400 at top" . 36.7) ("550 at bottom" . 36.7) ("550 at top" . 36.7))
  (2.9 ("300 at bottom" . 22.4) ("300 at top" . 27.4) ("350 at bottom" . 29.6) ("350 at top" . 36.7) ("400 at bottom" . 36.5) ("400 at top" . 36.7))
  (2.8 ("300 at bottom" . 24.0) ("300 at top" . 29.9) ("350 at bottom" . 30.5) ("350 at top" . 36.7) ("400 at bottom" . 36.7) ("400 at top" . 36.7))
  (2.7 ("300 at bottom" . 25.3) ("300 at top" . 32.6) ("350 at bottom" . 31.5) ("350 at top" . 36.7) ("400 at bottom" . 36.7) ("400 at top" . 36.7))
  (2.6 ("300 at bottom" . 26.2) ("300 at top" . 35.3) ("350 at bottom" . 32.7) ("350 at top" . 36.7) ("400 at bottom" . 36.7) ("400 at top" . 36.7))
  (2.5 ("250 at bottom" . 20.2) ("250 at top" . 24.8) ("300 at bottom" . 27.0) ("300 at top" . 36.7) ("350 at bottom" . 33.9) ("350 at top" . 36.7) ("400 at bottom" . 36.7) ("400 at top" . 36.7))
  (2.4 ("250 at bottom" . 21.3) ("250 at top" . 27.2) ("300 at bottom" . 27.8) ("300 at top" . 36.7) ("350 at bottom" . 35.0) ("350 at top" . 36.7) ("400 at bottom" . 36.7) ("400 at top" . 36.7))
  (2.3 ("250 at bottom" . 22.5) ("250 at top" . 29.5) ("300 at bottom" . 28.7) ("300 at top" . 36.7) ("350 at bottom" . 36.1) ("350 at top" . 36.7) ("400 at bottom" . 36.7) ("400 at top" . 36.7))
  (2.2 ("250 at bottom" . 23.3) ("250 at top" . 31.9) ("300 at bottom" . 29.8) ("300 at top" . 36.7) ("350 at bottom" . 36.7) ("350 at top" . 36.7) ("400 at bottom" . 36.7) ("400 at top" . 36.7))
  (2.1 ("250 at bottom" . 24.0) ("250 at top" . 34.3) ("300 at bottom" . 31.1) ("300 at top" . 36.7) ("350 at bottom" . 36.7) ("350 at top" . 36.7))
  (2.0 ("250 at bottom" . 24.6) ("250 at top" . 36.7) ("300 at bottom" . 32.4) ("300 at top" . 36.7) ("350 at bottom" . 36.7) ("350 at top" . 36.7))
  (1.9 ("250 at bottom" . 25.8) ("250 at top" . 36.7) ("300 at bottom" . 34.0) ("300 at top" . 36.7))
  (1.8 ("250 at bottom" . 26.9) ("250 at top" . 36.7) ("300 at bottom" . 35.6) ("300 at top" . 36.7))
  (1.7 ("250 at bottom" . 28.4) ("250 at top" . 36.7))
  (1.6 ("250 at bottom" . 30.1) ("250 at top" . 36.7))
  (1.5 ("250 at bottom" . 31.8) ("250 at top" . 36.7))
))


(defun CalculateTotalLoad (thickness)
  (setq h (/ thickness 1000.0))
  (setq concreteLoad (* h 25.0))
  (setq placingLoad (* 0.10 concreteLoad))
  (if (< placingLoad 0.75) (setq placingLoad 0.75))
  (if (> placingLoad 1.5) (setq placingLoad 1.5))
  (setq totalLoad (+ concreteLoad placingLoad 0.75 0.4))
  totalLoad
)

(defun GetMaxPropForThickness (thick)
  (setq data (cadr (assoc thick *FloorPropData*)))
  (setq maxP 0.0)
  (foreach pair data
    (if (> (car pair) maxP) (setq maxP (car pair)))
  )
  maxP
)

(defun GetInterpolatedBeamSpacing (thick targetProp / data sorted firstProp firstBeam lastProp lastBeam lower upper)
  (setq data (cadr (assoc thick *FloorPropData*)))
  (setq firstProp (caar data))
  (setq firstBeam (cadar data))
  (setq lastProp (car (last data)))
  (setq lastBeam (cadr (last data)))

  (if (<= targetProp firstProp)
      firstBeam
      (if (>= targetProp lastProp)
          lastBeam
          (progn
            (setq lower nil upper nil)
            (foreach pair (reverse data)
              (if (and (null lower) (<= (car pair) targetProp))
                  (setq lower pair)
              )
            )
            (foreach pair data
              (if (and (null upper) (>= (car pair) targetProp))
                  (setq upper pair)
              )
            )
            (if (= (car lower) (car upper))
                (cadr lower)
                (+ (cadr lower) (* (- targetProp (car lower)) (/ (- (cadr upper) (cadr lower)) (- (car upper) (car lower)))))
            )
          )
      )
  )
)

(defun GetPropCapacity (ext key / extData cap)
  (setq extData (cdr (assoc ext *PropCapacities*)))
  (if extData
      (setq cap (cdr (assoc key extData)))
      (setq cap nil)
  )
  cap
)


;; --- Global State for Persistence ---

(setq *glb_slab_thk* "300.0")
(setq *glb_floor_ht* "3000.0")
(setq *glb_prop_type* "300")
(setq *glb_prop_ori* "bottom")
(setq *glb_prop_spc* "1000.0")
(setq *glb_sec_cant* "500.0")
(setq *glb_usr_beam_spc* "")

;; Variables for Output screens
(setq *out_flex_beam_spc* "")
(setq *out_flex_act_ld* "")
(setq *out_flex_cap_lim* "")
(setq *out_flex_ut_rt* "")
(setq *out_flex_h20_shr* "")
(setq *out_flex_h20_ut* "")
(setq *glb_max_beam_spc_val* 0.0)

(defun WriteDCL ( / dclFile f )
  (setq dclFile (vl-filename-mktemp "EngDash.dcl"))
  (setq f (open dclFile "w"))

  (write-line "EngDashFlexIn : dialog { label = \"Flex Calculator Input\";" f)
  (write-line "  : column {" f)
  (write-line "    : edit_box { key = \"eb_slab_thk\"; label = \"Slab Thickness (mm):\"; edit_width = 12; }" f)
  (write-line "    : edit_box { key = \"eb_floor_ht\"; label = \"Floor Height (mm):\"; edit_width = 12; }" f)
  (write-line "    : popup_list { key = \"pl_prop_typ\"; label = \"Prop Type:\"; edit_width = 12; }" f)
  (write-line "    : popup_list { key = \"pl_prop_ori\"; label = \"Prop Orientation:\"; edit_width = 12; }" f)
  (write-line "    : edit_box { key = \"eb_prop_spc\"; label = \"Actual Prop Spacing (mm):\"; edit_width = 12; }" f)
  (write-line "    : edit_box { key = \"eb_sec_cant\"; label = \"Secondary Beam Cantilever (mm):\"; edit_width = 12; }" f)
  (write-line "    : row {" f)
  (write-line "      : button { key = \"btn_calc\"; label = \"Calculate\"; is_default = true; }" f)
  (write-line "      : button { key = \"cancel\"; label = \"Cancel\"; is_cancel = true; }" f)
  (write-line "    }" f)
  (write-line "  }" f)
  (write-line "}" f)

  (write-line "EngDashFlexOut : dialog { label = \"Flex Calculator Results\";" f)
  (write-line "  : column {" f)
  (write-line "    : text { key = \"txt_beam_spc\"; }" f)
  (write-line "    : text { key = \"txt_act_ld\"; }" f)
  (write-line "    : text { key = \"txt_cap_lim\"; }" f)
  (write-line "    : text { key = \"txt_ut_rt\"; }" f)
  (write-line "    : text { key = \"txt_h20_shr\"; }" f)
  (write-line "    : text { key = \"txt_h20_ut\"; }" f)
  (write-line "    : row {" f)
  (write-line "      : button { key = \"btn_back\"; label = \"Back\"; is_cancel = true; }" f)
  (write-line "      : button { key = \"accept\"; label = \"Proceed\"; is_default = true; }" f)
  (write-line "    }" f)
  (write-line "  }" f)
  (write-line "}" f)

  (write-line "EngDashBeamSpc : dialog { label = \"Beam Array\";" f)
  (write-line "  : column {" f)
  (write-line "    : text { key = \"txt_max_spc\"; }" f)
  (write-line "    : edit_box { key = \"eb_usr_spc\"; label = \"Primary Beam Spacing (mm):\"; edit_width = 12; }" f)
  (write-line "    : row {" f)
  (write-line "      : button { key = \"btn_back\"; label = \"Back\"; is_cancel = true; }" f)
  (write-line "      : button { key = \"accept\"; label = \"Proceed\"; is_default = true; }" f)
  (write-line "    }" f)
  (write-line "  }" f)
  (write-line "}" f)

  (close f)
  dclFile
)

(defun c:EngDashboard ( / dclFile dclID )
  (vl-load-com)
  (setq dclFile (WriteDCL))
  (setq dclID (load_dialog dclFile))

  (if (< dclID 0)
      (progn (princ "\nError loading DCL file.") (exit))
  )

  (RunFlexDialog dclID)

  (unload_dialog dclID)
  (vl-file-delete dclFile)
  (princ)
)

(defun RunFlexDialog ( dclID / flexLoop ret sT slabLoad x_vals x1 x2 maxP1 maxP2 interpolatedMaxProp z1 z2 finalZ currentBeamSpacing extensionMeters roundedExtension key vCap L P_m a a_over_L R_max propLoad vMax capacity actualPropLoad propCapLimit utilRate h20Shear h20Util val_thk val_fht val_spc val_can calc_success warningMsg pt_idx po_idx)
  (setq flexLoop T)
  (while flexLoop
    (if (not (new_dialog "EngDashFlexIn" dclID))
        (progn (princ "\nError displaying Flex Input Dialog.") (setq flexLoop nil) (exit))
    )

    (start_list "pl_prop_typ") (mapcar 'add_list '("250" "300" "350" "400" "550")) (end_list)
    (start_list "pl_prop_ori") (mapcar 'add_list '("bottom" "top")) (end_list)

    (setq pt_idx "1")
    (cond ((= *glb_prop_type* "250") (setq pt_idx "0"))
          ((= *glb_prop_type* "300") (setq pt_idx "1"))
          ((= *glb_prop_type* "350") (setq pt_idx "2"))
          ((= *glb_prop_type* "400") (setq pt_idx "3"))
          ((= *glb_prop_type* "550") (setq pt_idx "4")))

    (setq po_idx "0")
    (if (= *glb_prop_ori* "top") (setq po_idx "1"))

    (set_tile "eb_slab_thk" *glb_slab_thk*)
    (set_tile "eb_floor_ht" *glb_floor_ht*)
    (set_tile "pl_prop_typ" pt_idx)
    (set_tile "pl_prop_ori" po_idx)
    (set_tile "eb_prop_spc" *glb_prop_spc*)
    (set_tile "eb_sec_cant" *glb_sec_cant*)

    (action_tile "eb_slab_thk" "(setq *glb_slab_thk* $value)")
    (action_tile "eb_floor_ht" "(setq *glb_floor_ht* $value)")
    (action_tile "pl_prop_typ" "(setq idx (atoi $value)) (cond ((= idx 0) (setq *glb_prop_type* \"250\")) ((= idx 1) (setq *glb_prop_type* \"300\")) ((= idx 2) (setq *glb_prop_type* \"350\")) ((= idx 3) (setq *glb_prop_type* \"400\")) ((= idx 4) (setq *glb_prop_type* \"550\")) )")
    (action_tile "pl_prop_ori" "(setq idx (atoi $value)) (if (= idx 0) (setq *glb_prop_ori* \"bottom\") (setq *glb_prop_ori* \"top\"))")
    (action_tile "eb_prop_spc" "(setq *glb_prop_spc* $value)")
    (action_tile "eb_sec_cant" "(setq *glb_sec_cant* $value)")

    (action_tile "btn_calc" "(done_dialog 2)")
    (action_tile "cancel" "(done_dialog 0)")

    (setq ret (start_dialog))

    (if (= ret 2)
        (progn
          ;; PERFORM CALCULATION
          (setq val_thk (atof *glb_slab_thk*))
          (setq val_fht (atof *glb_floor_ht*))
          (setq val_spc (atof *glb_prop_spc*))
          (setq val_can (atof *glb_sec_cant*))
          (setq warningMsg "")

          (setq sT val_thk)
          (if (< sT 200.0) (setq sT 200.0))
          (if (> sT 500.0) (setq sT 500.0))
          (if (/= sT val_thk)
              (setq warningMsg (strcat "Warning: Slab Thickness adjusted to " (rtos sT 2 1) "mm. "))
          )

          (setq slabLoad (CalculateTotalLoad sT))

          (setq x_vals '(200.0 220.0 240.0 260.0 280.0 300.0 350.0 400.0 450.0 500.0))
          (setq x1 (car x_vals))
          (foreach x x_vals (if (<= x sT) (setq x1 x)))
          (setq x2 (last x_vals))
          (foreach x (reverse x_vals) (if (>= x sT) (setq x2 x)))
          (if (= x1 0) (setq x1 x2))
          (if (= x2 0) (setq x2 x1))

          (setq maxP1 (GetMaxPropForThickness x1))
          (setq maxP2 (GetMaxPropForThickness x2))

          (if (= x1 x2)
              (setq interpolatedMaxProp maxP1)
              (setq interpolatedMaxProp (+ maxP1 (* (- sT x1) (/ (- maxP2 maxP1) (- x2 x1)))))
          )

          (if (> val_spc interpolatedMaxProp)
              (progn
                (setq val_spc (float (fix (+ (* interpolatedMaxProp 10) 0.5))))
                (setq val_spc (/ val_spc 10.0))
                (setq *glb_prop_spc* (rtos val_spc 2 1))
                (setq warningMsg (strcat warningMsg "Max capacity exceeded. Prop spacing reduced to " (rtos val_spc 2 1) "mm."))
              )
          )

          (setq z1 (GetInterpolatedBeamSpacing x1 val_spc))
          (setq z2 (GetInterpolatedBeamSpacing x2 val_spc))

          (if (= x1 x2)
              (setq finalZ z1)
              (setq finalZ (+ z1 (* (- sT x1) (/ (- z2 z1) (- x2 x1)))))
          )

          (setq currentBeamSpacing (* (fix (/ finalZ 25.0)) 25.0))

          (setq extensionMeters (- (- (/ val_fht 1000.0) (/ sT 1000.0)) 0.418))
          (setq roundedExtension (/ (float (fix (+ (* extensionMeters 10) 0.9999))) 10.0))

          (setq key (strcat *glb_prop_type* " at " *glb_prop_ori*))
          (setq vCap 11.00)

          (setq calc_success T)
          (setq actualPropLoad 0.0 propCapLimit 0.0 utilRate 0.0 h20Shear 0.0 h20Util 0.0)

          (while calc_success
            (setq L (/ currentBeamSpacing 1000.0))
            (setq P_m (/ val_spc 1000.0))
            (setq a (/ val_can 1000.0))

            (setq R_max 0.0)
            (if (> L 0)
                (progn
                  (setq a_over_L (/ a L))
                  (if (<= a_over_L 0.4534)
                      (setq R_max (* slabLoad (- (* 1.1 L) (* 0.6 (/ (* a a) L)))))
                      (setq R_max (* slabLoad (+ a (* 0.4 L) (* 0.6 (/ (* a a) L)))))
                  )
                )
            )

            (setq propLoad (* R_max P_m))
            (setq vMax (* 0.5 R_max P_m))

            (setq capacity (GetPropCapacity roundedExtension key))

            (if (or (null capacity) (> propLoad capacity) (> vMax vCap))
                (progn
                  (setq currentBeamSpacing (- currentBeamSpacing 25.0))
                  (if (<= currentBeamSpacing 0)
                      (progn
                        (setq warningMsg "Error: Cannot find safe primary beam spacing.")
                        (setq currentBeamSpacing 0.0)
                        (setq calc_success nil)
                      )
                  )
                )
                (progn
                  (setq actualPropLoad propLoad)
                  (setq propCapLimit capacity)
                  (if (> capacity 0) (setq utilRate (* (/ propLoad capacity) 100.0)) (setq utilRate 0.0))
                  (setq h20Shear vMax)
                  (setq h20Util (* (/ vMax vCap) 100.0))
                  (setq calc_success nil)
                )
            )
          )

          (if (/= warningMsg "")
              (alert warningMsg)
          )

          (setq *glb_max_beam_spc_val* currentBeamSpacing)
          (if (= *glb_usr_beam_spc* "") (setq *glb_usr_beam_spc* (rtos *glb_max_beam_spc_val* 2 0)))

          (setq *out_flex_beam_spc* (strcat "Safe Primary Beam Spacing: " (rtos currentBeamSpacing 2 0) " mm"))
          (setq *out_flex_act_ld* (strcat "Actual Prop Load: " (rtos actualPropLoad 2 2) " kN"))
          (setq *out_flex_cap_lim* (strcat "Prop Capacity limit used: " (rtos propCapLimit 2 2) " kN"))
          (setq *out_flex_ut_rt* (strcat "Prop Utilization Rate: " (rtos utilRate 2 1) " %"))
          (setq *out_flex_h20_shr* (strcat "H20 Shear: " (rtos h20Shear 2 2) " kN"))
          (setq *out_flex_h20_ut* (strcat "H20 Utilization: " (rtos h20Util 2 1) " %"))

          ;; SHOW OUTPUT DIALOG
          (setq outLoop T)
          (while outLoop
            (if (not (new_dialog "EngDashFlexOut" dclID))
                (progn (princ "\nError displaying Flex Output Dialog.") (setq outLoop nil) (setq flexLoop nil))
            )
            (set_tile "txt_beam_spc" *out_flex_beam_spc*)
            (set_tile "txt_act_ld" *out_flex_act_ld*)
            (set_tile "txt_cap_lim" *out_flex_cap_lim*)
            (set_tile "txt_ut_rt" *out_flex_ut_rt*)
            (set_tile "txt_h20_shr" *out_flex_h20_shr*)
            (set_tile "txt_h20_ut" *out_flex_h20_ut*)

            (action_tile "btn_back" "(done_dialog 0)")
            (action_tile "accept" "(done_dialog 1)")

            (setq out_ret (start_dialog))
            (if (= out_ret 1)
                (progn
                    (setq outLoop nil)
                    (setq flexLoop nil)
                    ;; Proceed to Beam Array Dialog
                    (RunBeamArrayDialog dclID)
                )
                (setq outLoop nil) ;; Back button, loop continues in input
            )
          )
        )
        (setq flexLoop nil) ;; Cancel from input
    )
  )
)

(defun RunBeamArrayDialog ( dclID / beamLoop ret usr_spc max_str warningMsg)
  (setq beamLoop T)
  (while beamLoop
    (if (not (new_dialog "EngDashBeamSpc" dclID))
        (progn (princ "\nError displaying Beam Spacing Dialog.") (setq beamLoop nil) (exit))
    )

    (setq max_str (strcat "Max Allowed Primary Beam Spacing: " (rtos *glb_max_beam_spc_val* 2 0) " mm"))
    (set_tile "txt_max_spc" max_str)
    (set_tile "eb_usr_spc" *glb_usr_beam_spc*)

    (action_tile "eb_usr_spc" "(setq *glb_usr_beam_spc* $value)")

    (action_tile "btn_back" "(done_dialog 0)")
    (action_tile "accept" "(done_dialog 1)")

    (setq ret (start_dialog))

    (if (= ret 1)
        (progn
          (setq usr_spc (atof *glb_usr_beam_spc*))
          (if (> usr_spc *glb_max_beam_spc_val*)
              (progn
                (alert (strcat "Error: Input exceeds maximum allowed spacing (" (rtos *glb_max_beam_spc_val* 2 0) " mm)."))
              )
              (progn
                (setq beamLoop nil)
                ;; Trigger Array execution
                (DoBeamArray usr_spc)
              )
          )
        )
        (progn
          (setq beamLoop nil)
          ;; Go back to Flex Calculator
          (RunFlexDialog dclID)
        )
    )
  )
)

(defun DoBeamArray ( S_u / ent startPt endPt D ang lst cur_pt cur_dist obj )
  (setq ent (entsel "\nSelect line or polyline to array: "))
  (if (null ent)
      (progn (princ "\nNo entity selected.") (exit))
  )

  (setq startPt (getpoint "\nSelect Start Point: "))
  (if (null startPt) (exit))

  (setq endPt (getpoint startPt "\nSelect End Point: "))
  (if (null endPt) (exit))

  (setq D (distance startPt endPt))
  (setq ang (angle startPt endPt))

  (setq lst (ComputeSpacings S_u D))

  (if (null lst)
      (princ "\nDistance is too short to array.")
      (progn
        ;; Create copies
        (setq cur_dist 0.0)
        (foreach s lst
          (setq cur_dist (+ cur_dist s))
          (setq cur_pt (polar startPt ang cur_dist))
          (command "_.copy" (car ent) "" startPt cur_pt)
        )
        (princ (strcat "\nArray complete. Distance total: " (rtos cur_dist 2 2)))
      )
  )
)

;; The computation logic ensures:
;; 1. Last point is 500-700mm from endpoint. We choose to make L_last as close to 500 as possible.
;;    Actually, the easiest way is to leave exactly an integer multiple of 25mm such that the remainder is 500 <= Rem <= 700.
;;    We'll subtract 500. Then distribute S_u.
(defun ComputeSpacings ( S_u D / S_u_round L_last n rem total S1 S2 lst )
  ;; Round S_u to nearest 25mm down
  (setq S_u_round (* 25.0 (fix (/ (+ S_u 12.5) 25.0))))
  (if (> S_u_round S_u) (setq S_u_round (- S_u_round 25.0)))

  (if (<= D 500.0)
      nil
      (progn
        ;; Determine allowable length for array lines, leaving at least 500mm spacing.
        ;; So L_last = distance up to the final line.
        (setq L_last (* 25.0 (fix (/ (- D 500.0) 25.0))))
        (if (<= L_last 0.0)
            nil
            (progn
              (setq n (fix (/ (+ L_last 0.1) S_u_round)))
              (setq rem (- L_last (* n S_u_round)))
              (setq lst '())

              (if (> rem 1.0)
                  (if (< rem 1000.0)
                      (if (> n 0)
                          (progn
                            (setq total (+ S_u_round rem))
                            (setq S1 (* 25.0 (fix (/ (+ (/ total 2.0) 12.5) 25.0))))
                            (setq S2 (- total S1))
                            (setq n (- n 1))
                            (repeat n (setq lst (append lst (list S_u_round))))
                            (setq lst (append lst (list S1 S2)))
                          )
                          (setq lst (list rem))
                      )
                      (progn
                        (repeat n (setq lst (append lst (list S_u_round))))
                        (setq lst (append lst (list rem)))
                      )
                  )
                  (repeat n (setq lst (append lst (list S_u_round))))
              )
              lst
            )
        )
      )
  )
)
