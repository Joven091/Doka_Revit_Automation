(defun get-prop-capacities ()
  (list
    '(5.5 . (("250 at bottom" . nil) ("250 at top" . nil) ("300 at bottom" . nil) ("300 at top" . nil) ("350 at bottom" . nil) ("350 at top" . nil) ("400 at bottom" . nil) ("400 at top" . nil) ("550 at bottom" . 20.6) ("550 at top" . 22.7)))
    '(5.4 . (("250 at bottom" . nil) ("250 at top" . nil) ("300 at bottom" . nil) ("300 at top" . nil) ("350 at bottom" . nil) ("350 at top" . nil) ("400 at bottom" . nil) ("400 at top" . nil) ("550 at bottom" . 21.6) ("550 at top" . 23.9)))
    '(5.3 . (("250 at bottom" . nil) ("250 at top" . nil) ("300 at bottom" . nil) ("300 at top" . nil) ("350 at bottom" . nil) ("350 at top" . nil) ("400 at bottom" . nil) ("400 at top" . nil) ("550 at bottom" . 22.5) ("550 at top" . 25.2)))
    '(5.2 . (("250 at bottom" . nil) ("250 at top" . nil) ("300 at bottom" . nil) ("300 at top" . nil) ("350 at bottom" . nil) ("350 at top" . nil) ("400 at bottom" . nil) ("400 at top" . nil) ("550 at bottom" . 23.6) ("550 at top" . 26.5)))
    '(5.1 . (("250 at bottom" . nil) ("250 at top" . nil) ("300 at bottom" . nil) ("300 at top" . nil) ("350 at bottom" . nil) ("350 at top" . nil) ("400 at bottom" . nil) ("400 at top" . nil) ("550 at bottom" . 24.7) ("550 at top" . 27.9)))
    '(5.0 . (("250 at bottom" . nil) ("250 at top" . nil) ("300 at bottom" . nil) ("300 at top" . nil) ("350 at bottom" . nil) ("350 at top" . nil) ("400 at bottom" . nil) ("400 at top" . nil) ("550 at bottom" . 25.8) ("550 at top" . 29.4)))
    '(4.9 . (("250 at bottom" . nil) ("250 at top" . nil) ("300 at bottom" . nil) ("300 at top" . nil) ("350 at bottom" . nil) ("350 at top" . nil) ("400 at bottom" . nil) ("400 at top" . nil) ("550 at bottom" . 27.2) ("550 at top" . 31.0)))
    '(4.8 . (("250 at bottom" . nil) ("250 at top" . nil) ("300 at bottom" . nil) ("300 at top" . nil) ("350 at bottom" . nil) ("350 at top" . nil) ("400 at bottom" . nil) ("400 at top" . nil) ("550 at bottom" . 28.7) ("550 at top" . 32.5)))
    '(4.7 . (("250 at bottom" . nil) ("250 at top" . nil) ("300 at bottom" . nil) ("300 at top" . nil) ("350 at bottom" . nil) ("350 at top" . nil) ("400 at bottom" . nil) ("400 at top" . nil) ("550 at bottom" . 30.1) ("550 at top" . 34.2)))
    '(4.6 . (("250 at bottom" . nil) ("250 at top" . nil) ("300 at bottom" . nil) ("300 at top" . nil) ("350 at bottom" . nil) ("350 at top" . nil) ("400 at bottom" . nil) ("400 at top" . nil) ("550 at bottom" . 31.6) ("550 at top" . 35.9)))
    '(4.5 . (("250 at bottom" . nil) ("250 at top" . nil) ("300 at bottom" . nil) ("300 at top" . nil) ("350 at bottom" . nil) ("350 at top" . nil) ("400 at bottom" . nil) ("400 at top" . nil) ("550 at bottom" . 33.2) ("550 at top" . 36.7)))
    '(4.4 . (("250 at bottom" . nil) ("250 at top" . nil) ("300 at bottom" . nil) ("300 at top" . nil) ("350 at bottom" . nil) ("350 at top" . nil) ("400 at bottom" . nil) ("400 at top" . nil) ("550 at bottom" . 34.9) ("550 at top" . 36.7)))
    '(4.3 . (("250 at bottom" . nil) ("250 at top" . nil) ("300 at bottom" . nil) ("300 at top" . nil) ("350 at bottom" . nil) ("350 at top" . nil) ("400 at bottom" . nil) ("400 at top" . nil) ("550 at bottom" . 36.7) ("550 at top" . 36.7)))
    '(4.2 . (("250 at bottom" . nil) ("250 at top" . nil) ("300 at bottom" . nil) ("300 at top" . nil) ("350 at bottom" . nil) ("350 at top" . nil) ("400 at bottom" . nil) ("400 at top" . nil) ("550 at bottom" . 36.7) ("550 at top" . 36.7)))
    '(4.1 . (("250 at bottom" . nil) ("250 at top" . nil) ("300 at bottom" . nil) ("300 at top" . nil) ("350 at bottom" . nil) ("350 at top" . nil) ("400 at bottom" . nil) ("400 at top" . nil) ("550 at bottom" . 36.7) ("550 at top" . 36.7)))
    '(4.0 . (("250 at bottom" . nil) ("250 at top" . nil) ("300 at bottom" . nil) ("300 at top" . nil) ("350 at bottom" . nil) ("350 at top" . nil) ("400 at bottom" . 21.5) ("400 at top" . 24.8) ("550 at bottom" . 36.7) ("550 at top" . 36.7)))
    '(3.9 . (("250 at bottom" . nil) ("250 at top" . nil) ("300 at bottom" . nil) ("300 at top" . nil) ("350 at bottom" . nil) ("350 at top" . nil) ("400 at bottom" . 23.0) ("400 at top" . 26.8) ("550 at bottom" . 36.7) ("550 at top" . 36.7)))
    '(3.8 . (("250 at bottom" . nil) ("250 at top" . nil) ("300 at bottom" . nil) ("300 at top" . nil) ("350 at bottom" . nil) ("350 at top" . nil) ("400 at bottom" . 24.4) ("400 at top" . 28.7) ("550 at bottom" . 36.7) ("550 at top" . 36.7)))
    '(3.7 . (("250 at bottom" . nil) ("250 at top" . nil) ("300 at bottom" . nil) ("300 at top" . nil) ("350 at bottom" . nil) ("350 at top" . nil) ("400 at bottom" . 26.0) ("400 at top" . 30.8) ("550 at bottom" . 36.7) ("550 at top" . 36.7)))
    '(3.6 . (("250 at bottom" . nil) ("250 at top" . nil) ("300 at bottom" . nil) ("300 at top" . nil) ("350 at bottom" . nil) ("350 at top" . nil) ("400 at bottom" . 27.7) ("400 at top" . 33.2) ("550 at bottom" . 36.7) ("550 at top" . 36.7)))
    '(3.5 . (("250 at bottom" . nil) ("250 at top" . nil) ("300 at bottom" . nil) ("300 at top" . nil) ("350 at bottom" . 20.8) ("350 at top" . 24.5) ("400 at bottom" . 29.4) ("400 at top" . 35.5) ("550 at bottom" . 36.7) ("550 at top" . 36.7)))
    '(3.4 . (("250 at bottom" . nil) ("250 at top" . nil) ("300 at bottom" . nil) ("300 at top" . nil) ("350 at bottom" . 22.3) ("350 at top" . 26.7) ("400 at bottom" . 31.0) ("400 at top" . 36.7) ("550 at bottom" . 36.7) ("550 at top" . 36.7)))
    '(3.3 . (("250 at bottom" . nil) ("250 at top" . nil) ("300 at bottom" . nil) ("300 at top" . nil) ("350 at bottom" . 23.8) ("350 at top" . 28.9) ("400 at bottom" . 32.4) ("400 at top" . 36.7) ("550 at bottom" . 36.7) ("550 at top" . 36.7)))
    '(3.2 . (("250 at bottom" . nil) ("250 at top" . nil) ("300 at bottom" . nil) ("300 at top" . nil) ("350 at bottom" . 25.4) ("350 at top" . 31.3) ("400 at bottom" . 33.5) ("400 at top" . 36.7) ("550 at bottom" . 36.7) ("550 at top" . 36.7)))
    '(3.1 . (("250 at bottom" . nil) ("250 at top" . nil) ("300 at bottom" . nil) ("300 at top" . nil) ("350 at bottom" . 27.1) ("350 at top" . 34.0) ("400 at bottom" . 34.5) ("400 at top" . 36.7) ("550 at bottom" . 36.7) ("550 at top" . 36.7)))
    '(3.0 . (("250 at bottom" . nil) ("250 at top" . nil) ("300 at bottom" . 20.7) ("300 at top" . 24.8) ("350 at bottom" . 28.8) ("350 at top" . 36.7) ("400 at bottom" . 35.5) ("400 at top" . 36.7) ("550 at bottom" . 36.7) ("550 at top" . 36.7)))
    '(2.9 . (("250 at bottom" . nil) ("250 at top" . nil) ("300 at bottom" . 22.4) ("300 at top" . 27.4) ("350 at bottom" . 29.6) ("350 at top" . 36.7) ("400 at bottom" . 36.5) ("400 at top" . 36.7) ("550 at bottom" . nil) ("550 at top" . nil)))
    '(2.8 . (("250 at bottom" . nil) ("250 at top" . nil) ("300 at bottom" . 24.0) ("300 at top" . 29.9) ("350 at bottom" . 30.5) ("350 at top" . 36.7) ("400 at bottom" . 36.7) ("400 at top" . 36.7) ("550 at bottom" . nil) ("550 at top" . nil)))
    '(2.7 . (("250 at bottom" . nil) ("250 at top" . nil) ("300 at bottom" . 25.3) ("300 at top" . 32.6) ("350 at bottom" . 31.5) ("350 at top" . 36.7) ("400 at bottom" . 36.7) ("400 at top" . 36.7) ("550 at bottom" . nil) ("550 at top" . nil)))
    '(2.6 . (("250 at bottom" . nil) ("250 at top" . nil) ("300 at bottom" . 26.2) ("300 at top" . 35.3) ("350 at bottom" . 32.7) ("350 at top" . 36.7) ("400 at bottom" . 36.7) ("400 at top" . 36.7) ("550 at bottom" . nil) ("550 at top" . nil)))
    '(2.5 . (("250 at bottom" . 20.2) ("250 at top" . 24.8) ("300 at bottom" . 27.0) ("300 at top" . 36.7) ("350 at bottom" . 33.9) ("350 at top" . 36.7) ("400 at bottom" . 36.7) ("400 at top" . 36.7) ("550 at bottom" . nil) ("550 at top" . nil)))
    '(2.4 . (("250 at bottom" . 21.3) ("250 at top" . 27.2) ("300 at bottom" . 27.8) ("300 at top" . 36.7) ("350 at bottom" . 35.0) ("350 at top" . 36.7) ("400 at bottom" . 36.7) ("400 at top" . 36.7) ("550 at bottom" . nil) ("550 at top" . nil)))
    '(2.3 . (("250 at bottom" . 22.5) ("250 at top" . 29.5) ("300 at bottom" . 28.7) ("300 at top" . 36.7) ("350 at bottom" . 36.1) ("350 at top" . 36.7) ("400 at bottom" . 36.7) ("400 at top" . 36.7) ("550 at bottom" . nil) ("550 at top" . nil)))
    '(2.2 . (("250 at bottom" . 23.3) ("250 at top" . 31.9) ("300 at bottom" . 29.8) ("300 at top" . 36.7) ("350 at bottom" . 36.7) ("350 at top" . 36.7) ("400 at bottom" . 36.7) ("400 at top" . 36.7) ("550 at bottom" . nil) ("550 at top" . nil)))
    '(2.1 . (("250 at bottom" . 24.0) ("250 at top" . 34.3) ("300 at bottom" . 31.1) ("300 at top" . 36.7) ("350 at bottom" . 36.7) ("350 at top" . 36.7) ("400 at bottom" . nil) ("400 at top" . nil) ("550 at bottom" . nil) ("550 at top" . nil)))
    '(2.0 . (("250 at bottom" . 24.6) ("250 at top" . 36.7) ("300 at bottom" . 32.4) ("300 at top" . 36.7) ("350 at bottom" . 36.7) ("350 at top" . 36.7) ("400 at bottom" . nil) ("400 at top" . nil) ("550 at bottom" . nil) ("550 at top" . nil)))
    '(1.9 . (("250 at bottom" . 25.8) ("250 at top" . 36.7) ("300 at bottom" . 34.0) ("300 at top" . 36.7) ("350 at bottom" . nil) ("350 at top" . nil) ("400 at bottom" . nil) ("400 at top" . nil) ("550 at bottom" . nil) ("550 at top" . nil)))
    '(1.8 . (("250 at bottom" . 26.9) ("250 at top" . 36.7) ("300 at bottom" . 35.6) ("300 at top" . 36.7) ("350 at bottom" . nil) ("350 at top" . nil) ("400 at bottom" . nil) ("400 at top" . nil) ("550 at bottom" . nil) ("550 at top" . nil)))
    '(1.7 . (("250 at bottom" . 28.4) ("250 at top" . 36.7) ("300 at bottom" . nil) ("300 at top" . nil) ("350 at bottom" . nil) ("350 at top" . nil) ("400 at bottom" . nil) ("400 at top" . nil) ("550 at bottom" . nil) ("550 at top" . nil)))
    '(1.6 . (("250 at bottom" . 30.1) ("250 at top" . 36.7) ("300 at bottom" . nil) ("300 at top" . nil) ("350 at bottom" . nil) ("350 at top" . nil) ("400 at bottom" . nil) ("400 at top" . nil) ("550 at bottom" . nil) ("550 at top" . nil)))
    '(1.5 . (("250 at bottom" . 31.8) ("250 at top" . 36.7) ("300 at bottom" . nil) ("300 at top" . nil) ("350 at bottom" . nil) ("350 at top" . nil) ("400 at bottom" . nil) ("400 at top" . nil) ("550 at bottom" . nil) ("550 at top" . nil)))
  )
)

(defun get-dokafit-capacities ()
  (list
    '(4.0 . (("DokaFit Prop 300 at bottom" . nil) ("DokaFit Prop 300 at top" . nil) ("DokaFit Prop 300 at fixed" . nil) ("DokaFit Prop 350 at bottom" . nil) ("DokaFit Prop 350 at top" . nil) ("DokaFit Prop 350 at fixed" . nil) ("DokaFit Prop 400 at bottom" . 16.0) ("DokaFit Prop 400 at top" . 23.3) ("DokaFit Prop 400 at fixed" . 30.0)))
    '(3.9 . (("DokaFit Prop 300 at bottom" . nil) ("DokaFit Prop 300 at top" . nil) ("DokaFit Prop 300 at fixed" . nil) ("DokaFit Prop 350 at bottom" . nil) ("DokaFit Prop 350 at top" . nil) ("DokaFit Prop 350 at fixed" . nil) ("DokaFit Prop 400 at bottom" . 17.3) ("DokaFit Prop 400 at top" . 25.8) ("DokaFit Prop 400 at fixed" . 31.5)))
    '(3.8 . (("DokaFit Prop 300 at bottom" . nil) ("DokaFit Prop 300 at top" . nil) ("DokaFit Prop 300 at fixed" . nil) ("DokaFit Prop 350 at bottom" . nil) ("DokaFit Prop 350 at top" . nil) ("DokaFit Prop 350 at fixed" . nil) ("DokaFit Prop 400 at bottom" . 18.5) ("DokaFit Prop 400 at top" . 28.7) ("DokaFit Prop 400 at fixed" . 34.0)))
    '(3.7 . (("DokaFit Prop 300 at bottom" . nil) ("DokaFit Prop 300 at top" . nil) ("DokaFit Prop 300 at fixed" . nil) ("DokaFit Prop 350 at bottom" . nil) ("DokaFit Prop 350 at top" . nil) ("DokaFit Prop 350 at fixed" . nil) ("DokaFit Prop 400 at bottom" . 20.0) ("DokaFit Prop 400 at top" . 32.0) ("DokaFit Prop 400 at fixed" . 35.0)))
    '(3.6 . (("DokaFit Prop 300 at bottom" . nil) ("DokaFit Prop 300 at top" . nil) ("DokaFit Prop 300 at fixed" . nil) ("DokaFit Prop 350 at bottom" . nil) ("DokaFit Prop 350 at top" . nil) ("DokaFit Prop 350 at fixed" . nil) ("DokaFit Prop 400 at bottom" . 21.3) ("DokaFit Prop 400 at top" . 33.5) ("DokaFit Prop 400 at fixed" . 35.0)))
    '(3.5 . (("DokaFit Prop 300 at bottom" . nil) ("DokaFit Prop 300 at top" . nil) ("DokaFit Prop 300 at fixed" . nil) ("DokaFit Prop 350 at bottom" . 16.5) ("DokaFit Prop 350 at top" . 21.7) ("DokaFit Prop 350 at fixed" . 35.0) ("DokaFit Prop 400 at bottom" . 23.0) ("DokaFit Prop 400 at top" . 35.0) ("DokaFit Prop 400 at fixed" . 35.0)))
    '(3.4 . (("DokaFit Prop 300 at bottom" . nil) ("DokaFit Prop 300 at top" . nil) ("DokaFit Prop 300 at fixed" . nil) ("DokaFit Prop 350 at bottom" . 17.9) ("DokaFit Prop 350 at top" . 24.7) ("DokaFit Prop 350 at fixed" . 35.0) ("DokaFit Prop 400 at bottom" . 24.7) ("DokaFit Prop 400 at top" . 35.0) ("DokaFit Prop 400 at fixed" . 35.0)))
    '(3.3 . (("DokaFit Prop 300 at bottom" . nil) ("DokaFit Prop 300 at top" . nil) ("DokaFit Prop 300 at fixed" . nil) ("DokaFit Prop 350 at bottom" . 19.3) ("DokaFit Prop 350 at top" . 28.0) ("DokaFit Prop 350 at fixed" . 35.0) ("DokaFit Prop 400 at bottom" . 26.6) ("DokaFit Prop 400 at top" . 35.0) ("DokaFit Prop 400 at fixed" . 35.0)))
    '(3.2 . (("DokaFit Prop 300 at bottom" . nil) ("DokaFit Prop 300 at top" . nil) ("DokaFit Prop 300 at fixed" . nil) ("DokaFit Prop 350 at bottom" . 21.0) ("DokaFit Prop 350 at top" . 32.0) ("DokaFit Prop 350 at fixed" . 35.0) ("DokaFit Prop 400 at bottom" . 29.0) ("DokaFit Prop 400 at top" . 35.0) ("DokaFit Prop 400 at fixed" . 35.0)))
    '(3.1 . (("DokaFit Prop 300 at bottom" . nil) ("DokaFit Prop 300 at top" . nil) ("DokaFit Prop 300 at fixed" . nil) ("DokaFit Prop 350 at bottom" . 22.8) ("DokaFit Prop 350 at top" . 33.5) ("DokaFit Prop 350 at fixed" . 35.0) ("DokaFit Prop 400 at bottom" . 31.5) ("DokaFit Prop 400 at top" . 35.0) ("DokaFit Prop 400 at fixed" . 35.0)))
    '(3.0 . (("DokaFit Prop 300 at bottom" . 20.9) ("DokaFit Prop 300 at top" . 26.2) ("DokaFit Prop 300 at fixed" . 35.0) ("DokaFit Prop 350 at bottom" . 24.6) ("DokaFit Prop 350 at top" . 35.0) ("DokaFit Prop 350 at fixed" . 35.0) ("DokaFit Prop 400 at bottom" . 34.0) ("DokaFit Prop 400 at top" . 35.0) ("DokaFit Prop 400 at fixed" . 35.0)))
    '(2.9 . (("DokaFit Prop 300 at bottom" . 22.8) ("DokaFit Prop 300 at top" . 28.7) ("DokaFit Prop 300 at fixed" . 35.0) ("DokaFit Prop 350 at bottom" . 26.2) ("DokaFit Prop 350 at top" . 35.0) ("DokaFit Prop 350 at fixed" . 35.0) ("DokaFit Prop 400 at bottom" . 35.0) ("DokaFit Prop 400 at top" . 35.0) ("DokaFit Prop 400 at fixed" . 35.0)))
    '(2.8 . (("DokaFit Prop 300 at bottom" . 24.7) ("DokaFit Prop 300 at top" . 32.0) ("DokaFit Prop 300 at fixed" . 35.0) ("DokaFit Prop 350 at bottom" . 28.0) ("DokaFit Prop 350 at top" . 35.0) ("DokaFit Prop 350 at fixed" . 35.0) ("DokaFit Prop 400 at bottom" . 35.0) ("DokaFit Prop 400 at top" . 35.0) ("DokaFit Prop 400 at fixed" . 35.0)))
    '(2.7 . (("DokaFit Prop 300 at bottom" . 26.0) ("DokaFit Prop 300 at top" . 33.0) ("DokaFit Prop 300 at fixed" . 35.0) ("DokaFit Prop 350 at bottom" . 30.0) ("DokaFit Prop 350 at top" . 35.0) ("DokaFit Prop 350 at fixed" . 35.0) ("DokaFit Prop 400 at bottom" . 35.0) ("DokaFit Prop 400 at top" . 35.0) ("DokaFit Prop 400 at fixed" . 35.0)))
    '(2.6 . (("DokaFit Prop 300 at bottom" . 27.3) ("DokaFit Prop 300 at top" . 34.5) ("DokaFit Prop 300 at fixed" . 35.0) ("DokaFit Prop 350 at bottom" . 32.5) ("DokaFit Prop 350 at top" . 35.0) ("DokaFit Prop 350 at fixed" . 35.0) ("DokaFit Prop 400 at bottom" . 35.0) ("DokaFit Prop 400 at top" . 35.0) ("DokaFit Prop 400 at fixed" . 35.0)))
    '(2.5 . (("DokaFit Prop 300 at bottom" . 28.5) ("DokaFit Prop 300 at top" . 35.0) ("DokaFit Prop 300 at fixed" . 35.0) ("DokaFit Prop 350 at bottom" . 35.0) ("DokaFit Prop 350 at top" . 35.0) ("DokaFit Prop 350 at fixed" . 35.0) ("DokaFit Prop 400 at bottom" . 35.0) ("DokaFit Prop 400 at top" . 35.0) ("DokaFit Prop 400 at fixed" . 35.0)))
    '(2.4 . (("DokaFit Prop 300 at bottom" . 30.0) ("DokaFit Prop 300 at top" . 35.0) ("DokaFit Prop 300 at fixed" . 35.0) ("DokaFit Prop 350 at bottom" . 35.0) ("DokaFit Prop 350 at top" . 35.0) ("DokaFit Prop 350 at fixed" . 35.0) ("DokaFit Prop 400 at bottom" . nil) ("DokaFit Prop 400 at top" . nil) ("DokaFit Prop 400 at fixed" . nil)))
    '(2.3 . (("DokaFit Prop 300 at bottom" . 32.0) ("DokaFit Prop 300 at top" . 35.0) ("DokaFit Prop 300 at fixed" . 35.0) ("DokaFit Prop 350 at bottom" . 35.0) ("DokaFit Prop 350 at top" . 35.0) ("DokaFit Prop 350 at fixed" . 35.0) ("DokaFit Prop 400 at bottom" . nil) ("DokaFit Prop 400 at top" . nil) ("DokaFit Prop 400 at fixed" . nil)))
    '(2.2 . (("DokaFit Prop 300 at bottom" . 34.5) ("DokaFit Prop 300 at top" . 35.0) ("DokaFit Prop 300 at fixed" . 35.0) ("DokaFit Prop 350 at bottom" . 35.0) ("DokaFit Prop 350 at top" . 35.0) ("DokaFit Prop 350 at fixed" . 35.0) ("DokaFit Prop 400 at bottom" . nil) ("DokaFit Prop 400 at top" . nil) ("DokaFit Prop 400 at fixed" . nil)))
    '(2.1 . (("DokaFit Prop 300 at bottom" . 35.0) ("DokaFit Prop 300 at top" . 35.0) ("DokaFit Prop 300 at fixed" . 35.0) ("DokaFit Prop 350 at bottom" . 35.0) ("DokaFit Prop 350 at top" . 35.0) ("DokaFit Prop 350 at fixed" . 35.0) ("DokaFit Prop 400 at bottom" . nil) ("DokaFit Prop 400 at top" . nil) ("DokaFit Prop 400 at fixed" . nil)))
    '(2.0 . (("DokaFit Prop 300 at bottom" . 35.0) ("DokaFit Prop 300 at top" . 35.0) ("DokaFit Prop 300 at fixed" . 35.0) ("DokaFit Prop 350 at bottom" . 35.0) ("DokaFit Prop 350 at top" . 35.0) ("DokaFit Prop 350 at fixed" . 35.0) ("DokaFit Prop 400 at bottom" . nil) ("DokaFit Prop 400 at top" . nil) ("DokaFit Prop 400 at fixed" . nil)))
    '(1.9 . (("DokaFit Prop 300 at bottom" . 35.0) ("DokaFit Prop 300 at top" . 35.0) ("DokaFit Prop 300 at fixed" . 35.0) ("DokaFit Prop 350 at bottom" . nil) ("DokaFit Prop 350 at top" . nil) ("DokaFit Prop 350 at fixed" . nil) ("DokaFit Prop 400 at bottom" . nil) ("DokaFit Prop 400 at top" . nil) ("DokaFit Prop 400 at fixed" . nil)))
  )
)


;; --- H20 Data ---
(defun get-h20-data ()
  (list
    '("2.90m" . 1250.0)
    '("3.30m" . 950.0)
    '("3.60m" . 1050.0)
    '("3.90m" . 1150.0)
    '("4.50m" . 1000.0)
    '("4.90m" . 900.0)
  )
)

;; --- Constants ---
(setq MAX_H20_SHEAR_KN 11.00)
(setq MAX_H20_MOMENT_KNM 5.00)
(setq SYSTEM_DEPTH_METERS 0.418)
(setq H20_E_KN_M2 10760000.0)
(setq H20_I_M4 0.00004181)
(setq H20_EI (* H20_E_KN_M2 H20_I_M4))

;; --- Helper: Math.Round ---
(defun round-to (num places / mult)
  (setq mult (expt 10.0 places))
  (/ (float (fix (+ (* num mult) 0.5))) mult)
)

;; --- Helper: Get Capacity ---
(defun get-capacity (extension config-key / caps ext-data cap)
  (if (vl-string-search "DokaFit Prop" config-key)
    (setq caps (get-dokafit-capacities))
    (setq caps (get-prop-capacities))
  )

  (setq ext-data (cdr (assoc extension caps)))
  (if ext-data
    (progn
      (setq cap (cdr (assoc config-key ext-data)))
      (if (and cap (not (eq cap 'nil)))
        cap
        nil
      )
    )
    nil
  )
)

;; --- Helper: Slab Load ---
(defun calculate-total-load (thickness-mm custom-loads custom-live custom-formwork / h concrete-load placing-load)
  (if custom-loads
    (progn
      (setq h (/ thickness-mm 1000.0))
      (setq concrete-load (* h 25.0))
      (round-to (+ concrete-load custom-live custom-formwork) 2)
    )
    (progn
      (setq h (/ thickness-mm 1000.0))
      (setq concrete-load (* h 25.0))
      (setq placing-load (max 0.75 (min 1.5 (* 0.10 concrete-load))))
      (round-to (+ concrete-load placing-load 0.75 0.4) 2)
    )
  )
)

;; --- Math Multipliers ---
(defun get-max-deflection-multiplier (support-count L a / r r2 m1 m2 max-abs-defl u u2 u3 u4 term1 term2 term3 defl)
  (setq r (/ a L))
  (setq r2 (* r r))

  (cond
    ((<= support-count 2) (setq m1 (* 0.5 r2) m2 (* 0.5 r2)))
    ((= support-count 3)  (setq m1 (* 0.5 r2) m2 (- 0.125 (* 0.25 r2))))
    (t                    (setq m1 (* 0.5 r2) m2 (- 0.1 (* 0.1 r2))))
  )

  (setq max-abs-defl 0.0)
  (setq u 0.1)
  (while (<= u 0.95)
    (setq u2 (* u u))
    (setq u3 (* u2 u))
    (setq u4 (* u3 u))

    (setq term1 (/ (+ (- u (* 2 u3)) u4) 24.0))
    (setq term2 (/ (* m1 (+ (- (* 2 u) (* 3 u2)) u3)) 6.0))
    (setq term3 (/ (* m2 (- u u3)) 6.0))

    (setq defl (abs (- (- term1 term2) term3)))
    (if (> defl max-abs-defl)
      (setq max-abs-defl defl)
    )
    (setq u (+ u 0.05))
  )
  max-abs-defl
)

(defun get-max-reaction-multiplier (support-count L a / r1 r2)
  (cond
    ((<= support-count 2)
      (+ (/ L 2.0) a)
    )
    ((= support-count 3)
      (setq r1 (+ (* (/ 3.0 8.0) L) a (* (/ 3.0 4.0) (/ (* a a) L))))
      (setq r2 (- (* (/ 5.0 4.0) L) (* (/ 3.0 2.0) (/ (* a a) L))))
      (max r1 r2)
    )
    (t
      (setq r1 (+ (* 0.4 L) a (* 0.6 (/ (* a a) L))))
      (setq r2 (- (* 1.1 L) (* 0.6 (/ (* a a) L))))
      (max r1 r2)
    )
  )
)

(defun get-max-shear-multiplier (support-count L a / va v1 v2)
  (setq va a)
  (cond
    ((<= support-count 2)
      (max va (/ L 2.0))
    )
    ((= support-count 3)
      (setq v1 (abs (+ (* (/ 3.0 8.0) L) (* (/ 3.0 4.0) (/ (* a a) L)))))
      (setq v2 (abs (- (* (/ 5.0 8.0) L) (* (/ 3.0 4.0) (/ (* a a) L)))))
      (max va (max v1 v2))
    )
    (t
      (setq v1 (abs (+ (* 0.4 L) (* 0.6 (/ (* a a) L)))))
      (setq v2 (abs (- (* 0.6 L) (* 0.6 (/ (* a a) L)))))
      (max va (max v1 v2))
    )
  )
)

(defun get-max-moment-multiplier (support-count L a / ma m-span r1 x-sup m-sup m-int)
  (setq ma (/ (* a a) 2.0))
  (cond
    ((<= support-count 2)
      (setq m-span (abs (- (/ (* L L) 8.0) ma)))
      (max ma m-span)
    )
    ((= support-count 3)
      (setq r1 (+ (* (/ 3.0 8.0) L) a (* (/ 3.0 4.0) (/ (* a a) L))))
      (setq x-sup (- r1 a))
      (setq m-span (if (and (> x-sup 0) (< x-sup L))
                     (- (* r1 x-sup) (* 0.5 (expt (+ x-sup a) 2)))
                     0.0))
      (setq m-sup (abs (- (/ (* a a) 4.0) (/ (* L L) 8.0))))
      (max ma (max m-sup m-span))
    )
    (t
      (setq r1 (+ (* 0.4 L) a (* 0.6 (/ (* a a) L))))
      (setq x-sup (- r1 a))
      (setq m-span (if (and (> x-sup 0) (< x-sup L))
                     (- (* r1 x-sup) (* 0.5 (expt (+ x-sup a) 2)))
                     0.0))
      (setq m-sup (abs (- (/ (* a a) 10.0) (/ (* L L) 10.0))))
      (setq m-int (/ (* L L) 10.0))
      (max ma (max m-sup (max m-span m-int)))
    )
  )
)

;; --- DCL Builder ---
(defun generate-dcl ( / dcl-file f)
  (setq dcl-file (vl-filename-mktemp "flexcalc.dcl"))
  (setq f (open dcl-file "w"))
  (write-line "flexcalc_dlg : dialog {" f)
  (write-line "  label = \"Flex Calculator\";" f)

  (write-line "  : column {" f)
  (write-line "    : boxed_column {" f)
  (write-line "      label = \"Slab & Geometry\";" f)
  (write-line "      : edit_box { key = \"slabThickness\"; label = \"Slab Thickness (mm):\"; edit_width = 10; value=\"300\"; }" f)
  (write-line "      : edit_box { key = \"floorHeight\"; label = \"Floor Height (mm):\"; edit_width = 10; value=\"3000\"; }" f)
  (write-line "    }" f)

  (write-line "    : boxed_column {" f)
  (write-line "      label = \"Loads\";" f)
  (write-line "      : toggle { key = \"useCustomLoads\"; label = \"Use Custom Loads\"; }" f)
  (write-line "      : edit_box { key = \"customLiveLoad\"; label = \"Custom Live Load (kN/m2):\"; edit_width = 10; value=\"2.25\"; }" f)
  (write-line "      : edit_box { key = \"customFormworkLoad\"; label = \"Custom Formwork Load (kN/m2):\"; edit_width = 10; value=\"0.4\"; }" f)
  (write-line "    }" f)

  (write-line "    : boxed_column {" f)
  (write-line "      label = \"Secondary Beam Layout\";" f)
  (write-line "      : popup_list { key = \"primaryBeamCount\"; label = \"Primary Beam Count:\"; list = \"2\\n3\\n4+\"; value=\"1\"; }" f)
  (write-line "      : edit_box { key = \"secondaryBeamSpacing\"; label = \"Secondary Beam Spacing (mm):\"; edit_width = 10; value=\"488\"; }" f)
  (write-line "      : edit_box { key = \"secondaryBeamCantilever\"; label = \"Secondary Beam Cantilever (mm):\"; edit_width = 10; value=\"500\"; }" f)
  (write-line "      : popup_list { key = \"deflectionLimit\"; label = \"Deflection Limit:\"; list = \"L/500\\nL/350\\nL/270\"; value=\"1\"; }" f)
  (write-line "    }" f)

  (write-line "    : boxed_column {" f)
  (write-line "      label = \"Primary Beam & Prop Layout\";" f)
  (write-line "      : popup_list { key = \"propCount\"; label = \"Prop Count:\"; list = \"2\\n3\\n4+\"; value=\"1\"; }" f)
  (write-line "      : edit_box { key = \"propSpacing\"; label = \"Prop Spacing (mm):\"; edit_width = 10; value=\"1000\"; }" f)
  (write-line "      : edit_box { key = \"primaryBeamCantilever\"; label = \"Primary Beam Cantilever (mm):\"; edit_width = 10; value=\"500\"; }" f)
  (write-line "      : popup_list { key = \"propModel\"; label = \"Prop Model:\"; list = \"Prop Type Eurex eco 20\\nDokaFit Prop\"; value=\"0\"; }" f)
  (write-line "      : popup_list { key = \"propType\"; label = \"Prop Type:\"; }" f)
  (write-line "      : popup_list { key = \"propOrientation\"; label = \"Prop Orientation:\"; }" f)
  (write-line "    }" f)

  (write-line "    : button { key = \"calculate\"; label = \"Calculate\"; is_default = true; }" f)
  (write-line "    : boxed_column {" f)
  (write-line "      label = \"Results\";" f)
  (write-line "      : text { key = \"res_suggestedPrimaryBeamSpacing\"; value = \"Suggested Primary Beam Spacing: -\"; }" f)
  (write-line "      : text { key = \"res_actualPropLoad\"; value = \"Actual Prop Load: -\"; }" f)
  (write-line "      : text { key = \"res_propCapacityLimit\"; value = \"Prop Capacity Limit: -\"; }" f)
  (write-line "      : text { key = \"res_utilizationRate\"; value = \"Utilization Rate: -\"; }" f)
  (write-line "      : text { key = \"res_h20Shear\"; value = \"H20 Shear: -\"; }" f)
  (write-line "      : text { key = \"res_h20Utilization\"; value = \"H20 Utilization: -\"; }" f)
  (write-line "      : text { key = \"res_warningMessage\"; value = \"\"; }" f)
  (write-line "    }" f)
  (write-line "    ok_only;" f)
  (write-line "  }" f)
  (write-line "}" f)
  (close f)
  dcl-file
)

(defun update-prop-options (model / types orientations)
  (if (= model "Prop Type Eurex eco 20")
    (progn
      (start_list "propType") (mapcar 'add_list '("250" "300" "350" "400" "550")) (end_list)
      (set_tile "propType" "1")
      (start_list "propOrientation") (mapcar 'add_list '("at bottom" "at top")) (end_list)
      (set_tile "propOrientation" "0")
    )
    (progn
      (start_list "propType") (mapcar 'add_list '("300" "350" "400")) (end_list)
      (set_tile "propType" "0")
      (start_list "propOrientation") (mapcar 'add_list '("at bottom" "at top" "at fixed")) (end_list)
      (set_tile "propOrientation" "0")
    )
  )
)

;; --- Main Calculation ---
(defun do-calculate ( /
  slabThickness floorHeight useCustomLoads customLiveLoad customFormworkLoad
  primaryBeamCount secondaryBeamSpacing secondaryBeamCantilever deflectionLimit
  propCount propSpacing primaryBeamCantilever propModel propType propOrientation
  extensionMeters roundedExtension propKey capacity
  pbcInt pcInt w_slab a_s L_p a_p c_sec w_sb limit_denom
  v_cantilever_sec m_cantilever_sec defl_cantilever_sec limit_cantilever
  warnings test_L best_L_s v_sec m_sec defl_sec R_sec_multiplier w_pb v_prim m_prim p_prop
  suggestedPrimaryBeamSpacing final_L_s final_w_pb final_V_prim final_P_prop
  actualPropLoad h20Shear h20Utilization utilizationRate warningMessage
  )

  (setq slabThickness (atof (get_tile "slabThickness")))
  (setq floorHeight (atof (get_tile "floorHeight")))
  (setq useCustomLoads (= (get_tile "useCustomLoads") "1"))
  (setq customLiveLoad (atof (get_tile "customLiveLoad")))
  (setq customFormworkLoad (atof (get_tile "customFormworkLoad")))

  (setq pbcInt (cond ((= (get_tile "primaryBeamCount") "0") 2) ((= (get_tile "primaryBeamCount") "1") 3) (t 4)))
  (setq secondaryBeamSpacing (atof (get_tile "secondaryBeamSpacing")))
  (setq secondaryBeamCantilever (atof (get_tile "secondaryBeamCantilever")))

  (setq deflectionLimit (cond ((= (get_tile "deflectionLimit") "0") "L/500") ((= (get_tile "deflectionLimit") "1") "L/350") (t "L/270")))

  (setq pcInt (cond ((= (get_tile "propCount") "0") 2) ((= (get_tile "propCount") "1") 3) (t 4)))
  (setq propSpacing (atof (get_tile "propSpacing")))
  (setq primaryBeamCantilever (atof (get_tile "primaryBeamCantilever")))

  (setq propModel (if (= (get_tile "propModel") "0") "Prop Type Eurex eco 20" "DokaFit Prop"))

  (if (= propModel "Prop Type Eurex eco 20")
    (progn
      (setq propType (nth (atoi (get_tile "propType")) '("250" "300" "350" "400" "550")))
      (setq propOrientation (nth (atoi (get_tile "propOrientation")) '("at bottom" "at top")))
    )
    (progn
      (setq propType (nth (atoi (get_tile "propType")) '("300" "350" "400")))
      (setq propOrientation (nth (atoi (get_tile "propOrientation")) '("at bottom" "at top" "at fixed")))
    )
  )

  (setq warnings "")

  ;; 1. Capacity
  (setq extensionMeters (- (/ floorHeight 1000.0) (/ slabThickness 1000.0) SYSTEM_DEPTH_METERS))
  (setq roundedExtension (/ (float (fix (+ (* extensionMeters 10.0) 0.9999))) 10.0)) ; Ceiling

  (setq propKey (if (= propModel "DokaFit Prop")
                  (strcat "DokaFit Prop " propType " " propOrientation)
                  (strcat propType " " propOrientation)))

  (setq capacity (get-capacity roundedExtension propKey))

  (if (not capacity)
    (progn
      (set_tile "res_propCapacityLimit" "Prop Capacity Limit: 0")
      (set_tile "res_utilizationRate" "Utilization Rate: 0")
      (set_tile "res_suggestedPrimaryBeamSpacing" "Suggested Primary Beam Spacing: 0")
      (set_tile "res_actualPropLoad" "Actual Prop Load: 0")
      (set_tile "res_h20Shear" "H20 Shear: 0")
      (set_tile "res_h20Utilization" "H20 Utilization: 0")
      (set_tile "res_warningMessage" "Warning: Prop capacity data not found for this extension.")
    )
    (progn
      ;; 2. Convert Inputs
      (setq w_slab (calculate-total-load slabThickness useCustomLoads customLiveLoad customFormworkLoad))

      (setq a_s (/ secondaryBeamCantilever 1000.0))
      (setq L_p (/ propSpacing 1000.0))
      (setq a_p (/ primaryBeamCantilever 1000.0))
      (setq c_sec (/ secondaryBeamSpacing 1000.0))

      (setq w_sb (* w_slab c_sec))

      (setq limit_denom (cond ((= deflectionLimit "L/500") 500.0) ((= deflectionLimit "L/270") 270.0) (t 350.0)))

      ;; 3. Cantilever Limits
      (setq v_cantilever_sec (* w_sb a_s))
      (setq m_cantilever_sec (/ (* w_sb (expt a_s 2)) 2.0))
      (setq defl_cantilever_sec (/ (* w_sb (expt a_s 4)) (* 8.0 H20_EI)))
      (setq limit_cantilever (/ a_s limit_denom))

      (if (> v_cantilever_sec MAX_H20_SHEAR_KN)
        (setq warnings (strcat warnings " | Sec beam cantilever shear exceeds limit.")))
      (if (> m_cantilever_sec MAX_H20_MOMENT_KNM)
        (setq warnings (strcat warnings " | Sec beam cantilever moment exceeds limit.")))
      (if (and (> a_s 0) (> defl_cantilever_sec limit_cantilever))
        (setq warnings (strcat warnings " | Sec beam cantilever deflection exceeds limit.")))

      ;; 4. Solver
      (setq best_L_s 0.0)
      (if (= warnings "")
        (progn
          (setq test_L 4.00)
          (while (>= test_L 0.10)
            (setq v_sec (* w_sb (get-max-shear-multiplier pbcInt test_L a_s)))
            (setq m_sec (* w_sb (get-max-moment-multiplier pbcInt test_L a_s)))
            (setq defl_sec (* (/ (* w_sb (expt test_L 4)) H20_EI) (get-max-deflection-multiplier pbcInt test_L a_s)))

            (setq R_sec_multiplier (get-max-reaction-multiplier pbcInt test_L a_s))
            (setq w_pb (* w_slab R_sec_multiplier))

            (setq v_prim (* w_pb (get-max-shear-multiplier pcInt L_p a_p)))
            (setq m_prim (* w_pb (get-max-moment-multiplier pcInt L_p a_p)))
            (setq p_prop (* w_pb (get-max-reaction-multiplier pcInt L_p a_p)))

            (if (and (<= v_sec MAX_H20_SHEAR_KN)
                     (<= m_sec MAX_H20_MOMENT_KNM)
                     (<= defl_sec (/ test_L limit_denom))
                     (<= v_prim MAX_H20_SHEAR_KN)
                     (<= m_prim MAX_H20_MOMENT_KNM)
                     (<= p_prop capacity))
              (progn
                (setq best_L_s test_L)
                (setq test_L 0.0) ; break
              )
            )
            (setq test_L (- test_L 0.01))
          )
        )
      )

      ;; 5. Final Output
      (if (<= best_L_s 0)
        (progn
          (setq warnings (strcat warnings " | Cannot find valid primary beam spacing."))
          (set_tile "res_suggestedPrimaryBeamSpacing" "Suggested Primary Beam Spacing: 0")
          (set_tile "res_actualPropLoad" "Actual Prop Load: 0")
          (set_tile "res_propCapacityLimit" "Prop Capacity Limit: 0")
          (set_tile "res_utilizationRate" "Utilization Rate: 0")
          (set_tile "res_h20Shear" "H20 Shear: 0")
          (set_tile "res_h20Utilization" "H20 Utilization: 0")
        )
        (progn
          (setq suggestedPrimaryBeamSpacing (* (fix (/ (* best_L_s 1000.0) 25.0)) 25.0))
          (setq final_L_s (/ suggestedPrimaryBeamSpacing 1000.0))

          (setq final_w_pb (* w_slab (get-max-reaction-multiplier pbcInt final_L_s a_s)))
          (setq final_V_prim (* final_w_pb (get-max-shear-multiplier pcInt L_p a_p)))
          (setq final_P_prop (* final_w_pb (get-max-reaction-multiplier pcInt L_p a_p)))

          (set_tile "res_propCapacityLimit" (strcat "Prop Capacity Limit (kN): " (rtos capacity 2 2)))
          (set_tile "res_suggestedPrimaryBeamSpacing" (strcat "Suggested Primary Beam Spacing (mm): " (rtos suggestedPrimaryBeamSpacing 2 0)))
          (set_tile "res_actualPropLoad" (strcat "Actual Prop Load (kN): " (rtos final_P_prop 2 2)))
          (set_tile "res_utilizationRate" (strcat "Utilization Rate (%): " (rtos (* (/ final_P_prop capacity) 100.0) 2 1)))
          (set_tile "res_h20Shear" (strcat "H20 Shear (kN): " (rtos final_V_prim 2 2)))
          (set_tile "res_h20Utilization" (strcat "H20 Utilization (%): " (rtos (* (/ final_V_prim MAX_H20_SHEAR_KN) 100.0) 2 1)))
        )
      )
      (set_tile "res_warningMessage" warnings)
    )
  )
)

;; --- Command ---
(defun c:FlexCalc ( / dcl-id dcl-file)
  (vl-load-com)
  (setq dcl-file (generate-dcl))
  (setq dcl-id (load_dialog dcl-file))
  (if (not (new_dialog "flexcalc_dlg" dcl-id))
    (princ "\\nError: Could not load dialog.")
  )

  (update-prop-options "Prop Type Eurex eco 20")

  (action_tile "propModel" "(update-prop-options (nth (atoi $value) '(\"Prop Type Eurex eco 20\" \"DokaFit Prop\")))")
  (action_tile "calculate" "(do-calculate)")
  (action_tile "cancel" "(done_dialog)")

  (start_dialog)
  (unload_dialog dcl-id)
  (vl-file-delete dcl-file)
  (princ)
)
(princ "
Type 'FlexCalc' to start the Flex Calculator.")
(princ)
